-- NOTE: Various non-SMI text removed below (as indicated) for benefit of MIB
-- compiler.  Complete MIB text may be obtained at:
-- http://www.ietf.org/rfc/rfc3083.txt
-- Kevin O'Neal, 5/14/2001

-- CMTS-only definitions also removed
-- KO 7/25/2008

-- 1.  The SNMP Management Framework: REMOVED
-- 2.  Glossary: REMOVED
-- 3.  Overview: REMOVED

-- and we really start with...
-- 4.  Definitions


   DOCS-BPI-MIB DEFINITIONS ::= BEGIN

   IMPORTS
   MODULE-IDENTITY, OBJECT-TYPE,
   Integer32, Counter32, IpAddress
   FROM SNMPv2-SMI
   DisplayString, MacAddress, RowStatus, TruthValue, DateAndTime
   FROM SNMPv2-TC
   OBJECT-GROUP, MODULE-COMPLIANCE
   FROM SNMPv2-CONF
   ifIndex
   FROM IF-MIB
   docsIfMib, docsIfCmServiceId
   FROM DOCS-IF-MIB
   ;

   docsBpiMIB      MODULE-IDENTITY
   -- LAST-UPDATED "200103130000Z"
   LAST-UPDATED "0103130000Z"
   ORGANIZATION "IETF IPCDN Working Group"
   CONTACT-INFO "Rich Woundy
                 Postal: Cisco Systems
                         250 Apollo Drive
                         Chelmsford, MA 01824 U.S.A.
                 Tel: +1 978 244 8000
                 E-mail: rwoundy@cisco.com

                 IETF IPCDN Working Group
                 General Discussion: ipcdn@ietf.org
                 Subscribe: http://www.ietf.org/mailman/listinfo/ipcdn
                 Archive: ftp://ftp.ietf.org/ietf-mail-archive/ipcdn
                 Co-chairs: Richard Woundy, rwoundy@cisco.com
                            Andrew Valentine, a.valentine@eu.hns.com"
   DESCRIPTION
   "This is the MIB Module for the DOCSIS Baseline Privacy Interface
   (BPI) at cable modems (CMs) and cable modem termination systems
   (CMTSs). CableLabs requires the implementation of this MIB in
   DOCSIS 1.0 cable modems that implement the Baseline Privacy
   Interface, as a prerequisite for DOCSIS 1.0 certification."

   -- REVISION "200103130000Z"
   REVISION "0103130000Z"
   DESCRIPTION
   "Version published as RFC 3083."

   -- REVISION "200011031930Z"
   REVISION "0011031930Z"
   DESCRIPTION
   "Modified by Richard Woundy to fix problems identified by the MIB
   doctor. I marked docsBpiCmtsDefaultAuthGraceTime and
   docsBpiCmtsDefaultTEKGraceTime as obsolete objects, to prevent OID
   reassignment. Several object descriptions were also corrected."

   -- REVISION "200002161930Z"
   REVISION "0002161930Z"
   DESCRIPTION
   "Initial version.
   CableLabs requires the implementation of this MIB in certified DOCSIS
   1.0 cable modems implementing the Baseline Privacy Interface, per
   DOCSIS 1.0 engineering change notice oss-n-99027."
   ::= { docsIfMib 5 }

   docsBpiMIBObjects  OBJECT IDENTIFIER ::= { docsBpiMIB 1 }

   -- Cable Modem Group

   docsBpiCmObjects OBJECT IDENTIFIER ::= { docsBpiMIBObjects 1 }

   --
   -- The BPI base and authorization table for CMs, indexed by ifIndex
   --

   docsBpiCmBaseTable      OBJECT-TYPE
   SYNTAX                  SEQUENCE OF     DocsBpiCmBaseEntry
   MAX-ACCESS              not-accessible
   STATUS                  current
   DESCRIPTION
   "This table describes the basic and authorization-related Baseline
   Privacy attributes of each CM MAC interface."
   ::= { docsBpiCmObjects 1 }

   docsBpiCmBaseEntry      OBJECT-TYPE
   SYNTAX                  DocsBpiCmBaseEntry
   MAX-ACCESS              not-accessible
   STATUS                  current
   DESCRIPTION
   "Each entry contains objects describing attributes of one CM MAC
   interface. An entry in this table exists for each ifEntry with an
   ifType of docsCableMaclayer(127)."
   INDEX                   { ifIndex }
   ::= { docsBpiCmBaseTable 1 }

   DocsBpiCmBaseEntry ::= SEQUENCE {
   docsBpiCmPrivacyEnable                  TruthValue,
   docsBpiCmPublicKey                      OCTET STRING,
   docsBpiCmAuthState                      INTEGER,
   docsBpiCmAuthKeySequenceNumber          Integer32,
   docsBpiCmAuthExpires                    DateAndTime,
   docsBpiCmAuthReset                      TruthValue,
   docsBpiCmAuthGraceTime                  Integer32,
   docsBpiCmTEKGraceTime                   Integer32,
   docsBpiCmAuthWaitTimeout                Integer32,
   docsBpiCmReauthWaitTimeout              Integer32,
   docsBpiCmOpWaitTimeout                  Integer32,
   docsBpiCmRekeyWaitTimeout               Integer32,
   docsBpiCmAuthRejectWaitTimeout          Integer32,
   docsBpiCmAuthRequests                   Counter32,
   docsBpiCmAuthReplies                    Counter32,
   docsBpiCmAuthRejects                    Counter32,
   docsBpiCmAuthInvalids                   Counter32,
   docsBpiCmAuthRejectErrorCode            INTEGER,
   docsBpiCmAuthRejectErrorString          DisplayString,
   docsBpiCmAuthInvalidErrorCode           INTEGER,
   docsBpiCmAuthInvalidErrorString         DisplayString
   }

   docsBpiCmPrivacyEnable  OBJECT-TYPE
   SYNTAX                  TruthValue
   MAX-ACCESS              read-only
   STATUS                  current
   DESCRIPTION
   "This object identifies whether this CM is provisioned to run
   Baseline Privacy. This is analogous to the presence (or absence)
   of the Baseline Privacy Configuration Setting option. The status
   of each individual SID with respect to Baseline Privacy is
   captured in the docsBpiCmTEKPrivacyEnable object."
   REFERENCE
   "DOCSIS Baseline Privacy Interface Specification, Appendix A.1.1."
   ::= { docsBpiCmBaseEntry 1 }

   docsBpiCmPublicKey      OBJECT-TYPE
   SYNTAX                  OCTET STRING (SIZE (74 | 106 | 140 | 270))
   MAX-ACCESS              read-only
   STATUS                  current
   DESCRIPTION
   "The value of this object is a DER-encoded RSAPublicKey ASN.1 type
   string, as defined in the RSA Encryption Standard (PKCS #1) [22],
   corresponding to the public key of the CM. The 74, 106, 140, and
   270 byte key encoding lengths correspond to 512 bit, 768 bit, 1024
   bit, and 2048 public moduli respectively."
   REFERENCE
   "DOCSIS Baseline Privacy Interface Specification, Section 4.2.2.4."
   ::= { docsBpiCmBaseEntry 2 }

   docsBpiCmAuthState      OBJECT-TYPE
   SYNTAX                  INTEGER {
                                   start(1),
                                   authWait(2),
                                   authorized(3),
                                   reauthWait(4),
                                   authRejectWait(5)
                           }
   MAX-ACCESS              read-only
   STATUS                  current
   DESCRIPTION
   "The value of this object is the state of the CM authorization
   FSM.  The start state indicates that FSM is in its initial state."
   REFERENCE
   "DOCSIS Baseline Privacy Interface Specification, Section 4.1.2.1."
   ::= { docsBpiCmBaseEntry 3 }

   docsBpiCmAuthKeySequenceNumber  OBJECT-TYPE
   SYNTAX                          Integer32 (0..15)
   MAX-ACCESS                      read-only
   STATUS                          current
   DESCRIPTION
   "The value of this object is the authorization key sequence number
   for this FSM."
   REFERENCE
   "DOCSIS Baseline Privacy Interface Specification, Sections 4.2.1.2
   and 4.2.2.10."
   ::= { docsBpiCmBaseEntry 4 }

   docsBpiCmAuthExpires    OBJECT-TYPE
   SYNTAX                  DateAndTime
   MAX-ACCESS              read-only
   STATUS                  current
   DESCRIPTION
   "The value of this object is the actual clock time when the current
   authorization for this FSM expires. If the CM does not have an active
   authorization, then the value is of the expiration date and time of
   the last active authorization."
   REFERENCE
   "DOCSIS Baseline Privacy Interface Specification, Sections 4.2.1.2
   and 4.2.2.9."
   ::= { docsBpiCmBaseEntry 5 }

   docsBpiCmAuthReset      OBJECT-TYPE
   SYNTAX                  TruthValue
   MAX-ACCESS              read-write
   STATUS                  current
   DESCRIPTION
   "Setting this object to TRUE generates a Reauthorize event in the
   authorization FSM. Reading this object always returns FALSE."
   REFERENCE
   "DOCSIS Baseline Privacy Interface Specification, Section 4.1.2.3.4."
   ::= { docsBpiCmBaseEntry 6 }

   docsBpiCmAuthGraceTime  OBJECT-TYPE
   SYNTAX                  Integer32 (1..1800)
   UNITS                   "seconds"
   MAX-ACCESS              read-only
   STATUS                  current
   DESCRIPTION
   "The value of this object is the grace time for an authorization key.
   A CM is expected to start trying to get a new authorization key
   beginning AuthGraceTime seconds before the authorization key actually
   expires."
   REFERENCE
   "DOCSIS Baseline Privacy Interface Specification, Appendix A.1.1.1.3."
   ::= { docsBpiCmBaseEntry 7 }

   docsBpiCmTEKGraceTime   OBJECT-TYPE
   SYNTAX                  Integer32 (1..1800)
   UNITS                   "seconds"
   MAX-ACCESS              read-only
   STATUS                  current
   DESCRIPTION
   "The value of this object is the grace time for a TEK.  A CM is
   expected to start trying to get a new TEK beginning TEKGraceTime
   seconds before the TEK actually expires."
   REFERENCE
   "DOCSIS Baseline Privacy Interface Specification, Appendix A.1.1.1.6."
   ::= { docsBpiCmBaseEntry 8 }

   docsBpiCmAuthWaitTimeout        OBJECT-TYPE
   SYNTAX                          Integer32 (1..30)
   UNITS                           "seconds"
   MAX-ACCESS                      read-only
   STATUS                          current
   DESCRIPTION
   "The value of this object is the Authorize Wait Timeout."
   REFERENCE
   "DOCSIS Baseline Privacy Interface Specification, Appendix A.1.1.1.1."
   ::= { docsBpiCmBaseEntry 9 }

   docsBpiCmReauthWaitTimeout      OBJECT-TYPE
   SYNTAX                          Integer32 (1..30)
   UNITS                           "seconds"
   MAX-ACCESS                      read-only
   STATUS                          current
   DESCRIPTION
   "The value of this object is the Reauthorize Wait Timeout in seconds."
   REFERENCE
   "DOCSIS Baseline Privacy Interface Specification, Appendix A.1.1.1.2."
   ::= { docsBpiCmBaseEntry 10 }

   docsBpiCmOpWaitTimeout  OBJECT-TYPE
   SYNTAX                  Integer32 (1..10)
   UNITS                   "seconds"
   MAX-ACCESS              read-only
   STATUS                  current
   DESCRIPTION
   "The value of this object is the Operational Wait Timeout in seconds."
   REFERENCE
   "DOCSIS Baseline Privacy Interface Specification, Appendix A.1.1.1.4."
   ::= { docsBpiCmBaseEntry 11 }

   docsBpiCmRekeyWaitTimeout       OBJECT-TYPE
   SYNTAX                          Integer32 (1..10)
   UNITS                           "seconds"
   MAX-ACCESS                      read-only
   STATUS                          current
   DESCRIPTION
   "The value of this object is the Rekey Wait Timeout in seconds."
   REFERENCE
   "DOCSIS Baseline Privacy Interface Specification, Appendix A.1.1.1.5."
   ::= { docsBpiCmBaseEntry 12 }

   docsBpiCmAuthRejectWaitTimeout  OBJECT-TYPE
   SYNTAX                          Integer32 (1..600)
   UNITS                           "seconds"
   MAX-ACCESS                      read-only
   STATUS                          current
   DESCRIPTION
   "The value of this object is the Authorization Reject Wait Timeout in
   seconds."
   REFERENCE
   "DOCSIS Baseline Privacy Interface Specification, Appendix A.1.1.1.7."
   ::= { docsBpiCmBaseEntry 13 }

   docsBpiCmAuthRequests   OBJECT-TYPE
   SYNTAX                  Counter32
   MAX-ACCESS              read-only
   STATUS                  current
   DESCRIPTION
   "The value of this object is the count of times the CM has
   transmitted an Authorization Request message."
   REFERENCE
   "DOCSIS Baseline Privacy Interface Specification, Section 4.2.1.1."
   ::= { docsBpiCmBaseEntry 14 }

   docsBpiCmAuthReplies    OBJECT-TYPE
   SYNTAX                  Counter32
   MAX-ACCESS              read-only
   STATUS                  current
   DESCRIPTION
   "The value of this object is the count of times the CM has
   received an Authorization Reply message."
   REFERENCE
   "DOCSIS Baseline Privacy Interface Specification, Section 4.2.1.2."
   ::= { docsBpiCmBaseEntry 15 }

   docsBpiCmAuthRejects    OBJECT-TYPE
   SYNTAX                  Counter32
   MAX-ACCESS              read-only
   STATUS                  current
   DESCRIPTION
   "The value of this object is the count of times the CM has
   received an Authorization Reject message."
   REFERENCE
   "DOCSIS Baseline Privacy Interface Specification, Section 4.2.1.3."
   ::= { docsBpiCmBaseEntry 16 }

   docsBpiCmAuthInvalids   OBJECT-TYPE
   SYNTAX                  Counter32
   MAX-ACCESS              read-only
   STATUS                  current
   DESCRIPTION
   "The value of this object is the count of times the CM has
   received an Authorization Invalid message."
   REFERENCE
   "DOCSIS Baseline Privacy Interface Specification, Section 4.2.1.7."
   ::= { docsBpiCmBaseEntry 17 }

   docsBpiCmAuthRejectErrorCode    OBJECT-TYPE
   SYNTAX                          INTEGER {
                                           none(1),
                                           unknown(2),
                                           unauthorizedCm(3),
                                           unauthorizedSid(4)
                                   }
   MAX-ACCESS                      read-only
   STATUS                          current
   DESCRIPTION
   "The value of this object is the enumerated description of the
   Error-Code in most recent Authorization Reject message received by
   the CM.  This has value unknown(2) if the last Error-Code value was
   0, and none(1) if no Authorization Reject message has been received
   since reboot."
   REFERENCE
   "DOCSIS Baseline Privacy Interface Specification, Sections 4.2.1.3
   and 4.2.2.16."
   ::= { docsBpiCmBaseEntry 18 }

   docsBpiCmAuthRejectErrorString  OBJECT-TYPE
   SYNTAX                          DisplayString (SIZE (0..128))
   MAX-ACCESS                      read-only
   STATUS                          current
   DESCRIPTION
   "The value of this object is the Display-String in most recent
   Authorization Reject message received by the CM.  This is a zero
   length string if no Authorization Reject message has been received
   since reboot."
   REFERENCE
   "DOCSIS Baseline Privacy Interface Specification, Sections 4.2.1.3
   and 4.2.2.6."
   ::= { docsBpiCmBaseEntry 19 }

   docsBpiCmAuthInvalidErrorCode   OBJECT-TYPE
   SYNTAX                  INTEGER {
                                   none(1),
                                   unknown(2),
                                   unauthorizedCm(3),
                                   unsolicited(5),
                                   invalidKeySequence(6),
                                   keyRequestAuthenticationFailure(7)
                           }
   MAX-ACCESS              read-only
   STATUS                  current
   DESCRIPTION
   "The value of this object is the enumerated description of the
   Error-Code in most recent Authorization Invalid message received by
   the CM.  This has value unknown(2) if the last Error-Code value was
   0, and none(1) if no Authorization Invalid message has been received
   since reboot."
   REFERENCE
   "DOCSIS Baseline Privacy Interface Specification, Sections 4.2.1.7
   and 4.2.2.16."
   ::= { docsBpiCmBaseEntry 20 }

   docsBpiCmAuthInvalidErrorString OBJECT-TYPE
   SYNTAX                          DisplayString (SIZE (0..128))
   MAX-ACCESS                      read-only
   STATUS                          current
   DESCRIPTION
   "The value of this object is the Display-String in most recent
   Authorization Invalid message received by the CM.  This is a zero
   length string if no Authorization Invalid message has been received
   since reboot."
   REFERENCE
   "DOCSIS Baseline Privacy Interface Specification, Sections 4.2.1.7
   and 4.2.2.6."
   ::= { docsBpiCmBaseEntry 21 }

   --
   -- The CM TEK Table, indexed by ifIndex and SID
   --

   docsBpiCmTEKTable       OBJECT-TYPE
   SYNTAX                  SEQUENCE OF     DocsBpiCmTEKEntry
   MAX-ACCESS              not-accessible
   STATUS                  current
   DESCRIPTION
   "This table describes the attributes of each CM Traffic Encryption Key
   (TEK) association. The CM maintains (no more than) one TEK association
   per SID per CM MAC interface."
   ::= { docsBpiCmObjects 2 }

   docsBpiCmTEKEntry       OBJECT-TYPE
   SYNTAX                  DocsBpiCmTEKEntry
   MAX-ACCESS              not-accessible
   STATUS                  current
   DESCRIPTION
   "Each entry contains objects describing the TEK association attributes
   of one SID. The CM MUST create one entry per unicast SID, regardless
   of whether the SID was obtained from a Registration Response message,
   or from an Authorization Reply message."
   INDEX                   { ifIndex, docsIfCmServiceId }
   ::= { docsBpiCmTEKTable 1 }

   DocsBpiCmTEKEntry ::= SEQUENCE {
   docsBpiCmTEKPrivacyEnable               TruthValue,
   docsBpiCmTEKState                       INTEGER,
   docsBpiCmTEKExpiresOld                  DateAndTime,
   docsBpiCmTEKExpiresNew                  DateAndTime,
   docsBpiCmTEKKeyRequests                 Counter32,
   docsBpiCmTEKKeyReplies                  Counter32,
   docsBpiCmTEKKeyRejects                  Counter32,
   docsBpiCmTEKInvalids                    Counter32,
   docsBpiCmTEKAuthPends                   Counter32,
   docsBpiCmTEKKeyRejectErrorCode          INTEGER,
   docsBpiCmTEKKeyRejectErrorString        DisplayString,
   docsBpiCmTEKInvalidErrorCode            INTEGER,
   docsBpiCmTEKInvalidErrorString          DisplayString
   }

   docsBpiCmTEKPrivacyEnable       OBJECT-TYPE
   SYNTAX                          TruthValue
   MAX-ACCESS                      read-only
   STATUS                          current
   DESCRIPTION
   "This object identifies whether this SID is provisioned to run
   Baseline Privacy. This is analogous to enabling Baseline Privacy on
   a provisioned SID using the Class-of-Service Privacy Enable option.
   Baseline Privacy is not effectively enabled for any SID unless
   Baseline Privacy is enabled for the CM, which is managed via the
   docsBpiCmPrivacyEnable object."
   REFERENCE
   "DOCSIS Baseline Privacy Interface Specification, Appendix A.1.2."
   ::= { docsBpiCmTEKEntry 1 }

   docsBpiCmTEKState       OBJECT-TYPE
   SYNTAX                  INTEGER {
                                   start(1),
                                   opWait(2),
                                   opReauthWait(3),
                                   operational(4),
                                   rekeyWait(5),
                                   rekeyReauthWait(6)
                           }
   MAX-ACCESS              read-only
   STATUS                  current
   DESCRIPTION
   "The value of this object is the state of the indicated TEK FSM.
   The start(1) state indicates that FSM is in its initial state."
   REFERENCE
   "DOCSIS Baseline Privacy Interface Specification, Section 4.1.3.1."
   ::= { docsBpiCmTEKEntry 2 }

   docsBpiCmTEKExpiresOld  OBJECT-TYPE
   SYNTAX                  DateAndTime
   MAX-ACCESS              read-only
   STATUS                  current
   DESCRIPTION
   "The value of this object is the actual clock time for expiration
   of the immediate predecessor of the most recent TEK for this FSM.
   If this FSM has only one TEK, then the value is the time of activation
   of this FSM."
   REFERENCE
   "DOCSIS Baseline Privacy Interface Specification, Sections 4.2.1.5 and
   4.2.2.9."
   ::= { docsBpiCmTEKEntry 3 }

   docsBpiCmTEKExpiresNew  OBJECT-TYPE
   SYNTAX                  DateAndTime
   MAX-ACCESS              read-only
   STATUS                  current
   DESCRIPTION
   "The value of this object is the actual clock time for expiration
   of the most recent TEK for this FSM."
   REFERENCE
   "DOCSIS Baseline Privacy Interface Specification, Sections 4.2.1.5 and
   4.2.2.9."
   ::= { docsBpiCmTEKEntry 4 }

   docsBpiCmTEKKeyRequests OBJECT-TYPE
   SYNTAX                  Counter32
   MAX-ACCESS              read-only
   STATUS                  current
   DESCRIPTION
   "The value of this object is the count of times the CM has transmitted
   a Key Request message."
   REFERENCE
   "DOCSIS Baseline Privacy Interface Specification, Section 4.2.1.4."
   ::= { docsBpiCmTEKEntry 5 }

   docsBpiCmTEKKeyReplies  OBJECT-TYPE
   SYNTAX                  Counter32
   MAX-ACCESS              read-only
   STATUS                  current
   DESCRIPTION
   "The value of this object is the count of times the CM has received
   a Key Reply message, including a message whose authentication failed."
   REFERENCE
   "DOCSIS Baseline Privacy Interface Specification, Section 4.2.1.5."
   ::= { docsBpiCmTEKEntry 6 }

   docsBpiCmTEKKeyRejects  OBJECT-TYPE
   SYNTAX                  Counter32
   MAX-ACCESS              read-only
   STATUS                  current
   DESCRIPTION
   "The value of this object is the count of times the CM has received
   a Key Reject message, including a message whose authentication failed."
   REFERENCE
   "DOCSIS Baseline Privacy Interface Specification, Section 4.2.1.6."
   ::= { docsBpiCmTEKEntry 7 }

   docsBpiCmTEKInvalids    OBJECT-TYPE
   SYNTAX                  Counter32
   MAX-ACCESS              read-only
   STATUS                  current
   DESCRIPTION
   "The value of this object is the count of times the CM has received
   a TEK Invalid message, including a message whose authentication failed."
   REFERENCE
   "DOCSIS Baseline Privacy Interface Specification, Section 4.2.1.8."
   ::= { docsBpiCmTEKEntry 8 }

   docsBpiCmTEKAuthPends   OBJECT-TYPE
   SYNTAX                  Counter32
   MAX-ACCESS              read-only
   STATUS                  current
   DESCRIPTION
   "The value of this object is the count of times an Authorization
   Pending (Auth Pend) event occurred in this FSM."
   REFERENCE
   "DOCSIS Baseline Privacy Interface Specification, Section 4.1.3.3.3."
   ::= { docsBpiCmTEKEntry 9 }

   docsBpiCmTEKKeyRejectErrorCode  OBJECT-TYPE
   SYNTAX                          INTEGER {
                                           none(1),
                                           unknown(2),
                                           unauthorizedSid(4)
                                   }
   MAX-ACCESS                      read-only
   STATUS                          current
   DESCRIPTION
   "The value of this object is the enumerated description of the
   Error-Code in most recent Key Reject message received by the CM. This
   has value unknown(2) if the last Error-Code value was 0, and none(1)
   if no Key Reject message has been received since reboot."
   REFERENCE
   "DOCSIS Baseline Privacy Interface Specification, Sections 4.1.2.6
   and 4.2.2.16."
   ::= { docsBpiCmTEKEntry 10 }

   docsBpiCmTEKKeyRejectErrorString        OBJECT-TYPE
   SYNTAX                                  DisplayString (SIZE (0..128))
   MAX-ACCESS                              read-only
   STATUS                                  current
   DESCRIPTION
   "The value of this object is the Display-String in most recent Key
   Reject message received by the CM. This is a zero length string if no
   Key Reject message has been received since reboot."
   REFERENCE
   "DOCSIS Baseline Privacy Interface Specification, Sections 4.1.2.6
   and 4.2.2.6."
   ::= { docsBpiCmTEKEntry 11 }
   docsBpiCmTEKInvalidErrorCode    OBJECT-TYPE
   SYNTAX                          INTEGER {
                                           none(1),
                                           unknown(2),
                                           invalidKeySequence(6)
                                   }
   MAX-ACCESS                      read-only
   STATUS                          current
   DESCRIPTION
   "The value of this object is the enumerated description of the
   Error-Code in most recent TEK Invalid message received by the CM.
   This has value unknown(2) if the last Error-Code value was 0, and
   none(1) if no TEK Invalid message has been received since reboot."
   REFERENCE
   "DOCSIS Baseline Privacy Interface Specification, Sections 4.1.2.8
   and 4.2.2.16."
   ::= { docsBpiCmTEKEntry 12 }

   docsBpiCmTEKInvalidErrorString  OBJECT-TYPE
   SYNTAX                          DisplayString (SIZE (0..128))
   MAX-ACCESS                      read-only
   STATUS                          current
   DESCRIPTION
   "The value of this object is the Display-String in most recent TEK
   Invalid message received by the CM. This is a zero length string if
   no TEK Invalid message has been received since reboot."
   REFERENCE
   "DOCSIS Baseline Privacy Interface Specification, Sections 4.1.2.8
   and 4.2.2.6."
   ::= { docsBpiCmTEKEntry 13 }

   --
   -- The BPI MIB Conformance Statements (with a placeholder for
   -- notifications)
   --

   docsBpiNotification     OBJECT IDENTIFIER ::= { docsBpiMIB 2 }
   docsBpiConformance      OBJECT IDENTIFIER ::= { docsBpiMIB 3 }
   docsBpiCompliances      OBJECT IDENTIFIER ::= { docsBpiConformance 1 }
   docsBpiGroups           OBJECT IDENTIFIER ::= { docsBpiConformance 2 }

   docsBpiBasicCompliance MODULE-COMPLIANCE
   STATUS          current
   DESCRIPTION
   "This is the compliance statement for devices which implement the
   DOCSIS Baseline Privacy Interface."

   MODULE  -- docsBpiMIB

   -- conditionally mandatory group
   GROUP   docsBpiCmGroup
   DESCRIPTION
   "This group is implemented only in CMs, not in CMTSs."
   
   ::= { docsBpiCompliances 1 }

   docsBpiCmGroup  OBJECT-GROUP
   OBJECTS {
   docsBpiCmPrivacyEnable,
   docsBpiCmPublicKey,
   docsBpiCmAuthState,
   docsBpiCmAuthKeySequenceNumber,
   docsBpiCmAuthExpires,
   docsBpiCmAuthReset,
   docsBpiCmAuthGraceTime,
   docsBpiCmTEKGraceTime,
   docsBpiCmAuthWaitTimeout,
   docsBpiCmReauthWaitTimeout,
   docsBpiCmOpWaitTimeout,
   docsBpiCmRekeyWaitTimeout,
   docsBpiCmAuthRejectWaitTimeout,
   docsBpiCmAuthRequests,
   docsBpiCmAuthReplies,
   docsBpiCmAuthRejects,
   docsBpiCmAuthInvalids,
   docsBpiCmAuthRejectErrorCode,
   docsBpiCmAuthRejectErrorString,
   docsBpiCmAuthInvalidErrorCode,
   docsBpiCmAuthInvalidErrorString,
   docsBpiCmTEKPrivacyEnable,
   docsBpiCmTEKState,
   docsBpiCmTEKExpiresOld,
   docsBpiCmTEKExpiresNew,
   docsBpiCmTEKKeyRequests,
   docsBpiCmTEKKeyReplies,
   docsBpiCmTEKKeyRejects,
   docsBpiCmTEKInvalids,
   docsBpiCmTEKAuthPends,
   docsBpiCmTEKKeyRejectErrorCode,
   docsBpiCmTEKKeyRejectErrorString,
   docsBpiCmTEKInvalidErrorCode,
   docsBpiCmTEKInvalidErrorString
   }
   STATUS                  current
   DESCRIPTION
   "This collection of objects provides CM BPI status and control."
   ::= { docsBpiGroups 1 }

   docsBpiObsoleteObjectsGroup     OBJECT-GROUP
   OBJECTS {
   docsBpiCmtsDefaultAuthGraceTime,
   docsBpiCmtsDefaultTEKGraceTime
   }
   STATUS          obsolete
   DESCRIPTION
   "This is a collection of obsolete BPI objects."
   ::= { docsBpiGroups 3 }

   END

-- 5.  Acknowledgments: REMOVED
-- 6.  References: REMOVED
-- 7.  Security Considerations: REMOVED
-- 8.  Intellectual Property: REMOVED
-- 9.  Author's Address: REMOVED
-- 10.  Full Copyright Statement: REMOVED
