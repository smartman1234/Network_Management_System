--
-- From http://www.packetcable.com/downloads/specs/CL-SP-MIB-BB-I01-050128.txt
--
-- This MIB is a CableLabs document describing UPS-MIB requirements in the
-- context of CableLabs certified products in general, and PacketCable 1.5
-- in particular.  It does not introduce any new objects, it is mainly a
-- conformance section identifying required objects and some additional details
-- regarding UPS-MIB implementation in this context.
--

CLAB-UPS-MIB DEFINITIONS ::= BEGIN

IMPORTS
    MODULE-IDENTITY         FROM SNMPv2-SMI      -- RFC 2578
    MODULE-COMPLIANCE       FROM SNMPv2-CONF     -- RFC 2580

    clabCommonMibs          FROM CLAB-DEF-MIB

    upsIdentManufacturer,
    upsIdentModel,
    upsIdentAgentSoftwareVersion,
    upsIdentName,
    upsIdentAttachedDevices,
    upsBatteryStatus,
    upsSecondsOnBattery,
    upsEstimatedMinutesRemaining,
    upsEstimatedChargeRemaining,
    upsInputLineBads,                           -- optional
    upsInputNumLines,
    upsInputFrequency,                          -- optional
    upsInputVoltage,                            -- optional 
    upsOutputSource, 
    upsOutputFrequency,                         -- optional
    upsOutputNumLines, 
    upsOutputVoltage,                           -- optional
    upsAlarmsPresent,
    upsAlarmDescr,
    upsAlarmTime,
    upsShutdownType, 
    upsShutdownAfterDelay,
    upsStartupAfterDelay,
    upsRebootWithDuration,
    upsAutoRestart,                             -- optional
    upsConfigInputVoltage,                      -- optional
    upsConfigInputFreq,                         -- optional
    upsConfigOutputVoltage,                     -- optional
    upsConfigOutputFreq,                        -- optional
    upsConfigOutputVA,                          -- optional
    upsConfigOutputPower,                       -- optional
    upsConfigLowBattTime,
    upsConfigAudibleStatus                      -- optional
                            FROM UPS-MIB;       -- RFC 1628



clabUpsMib MODULE-IDENTITY
    LAST-UPDATED "200501280000Z" -- January 28, 2005
    ORGANIZATION "Cable Television Laboratories, Inc."
    CONTACT-INFO
            "Sumanth Channabasappa - CableLabs
             Postal: Cable Television Laboratories, Inc
             858 Coal Creek Circle
             Louisville, CO 80027
             U.S.A.
             Phone: +1 303 661 9100
             Fax: +1-303 661-9199
             E-mail:mibs@cablelabs.com

             Acknowledgements:
             Jean-Francois Mule – CableLabs, Inc.
             Kevin Marez, Motorola, Inc."
    DESCRIPTION
            "This MIB module provides the management objects for the
             configuration and monitoring of the battery backup &amp; UPS
             functionality for CableLabs compliant devices."

    ::= { clabCommonMibs 1 }


-- Administrative assignments

clabUpsNotifications OBJECT IDENTIFIER ::= { clabUpsMib 0 }
clabUpsObjects       OBJECT IDENTIFIER ::= { clabUpsMib 1 }
clabUpsConformance   OBJECT IDENTIFIER ::= { clabUpsMib 2 }


-- Object Groups
-- The object groups used in this MIB module are imported from 
-- the IETF RFC 1628, see the module compliance statement


-- Conformance Statements
   clabUpsCompliances OBJECT IDENTIFIER ::=
                                           { clabUpsConformance 1 }
   clabUpsGroups OBJECT IDENTIFIER      ::=
                                           { clabUpsConformance 2 }


clabUpsMibCompliance MODULE-COMPLIANCE
       STATUS     current
       DESCRIPTION
               "The compliance statement for CableLabs compliant
                devices that implement battery backup and UPS
                functionality."

       MODULE UPS-MIB -- RFC 1628
           MANDATORY-GROUPS  { 
                     upsSubsetIdentGroup,
                     upsFullBatteryGroup, 
                     upsBasicInputGroup,
                     upsBasicOutputGroup, 
                     upsBasicAlarmGroup,
                     upsBasicControlGroup,
                     upsBasicConfigGroup  
                     }


   -- upsSubsetIdentGroup OBJECT-GROUP
   --    OBJECTS { upsIdentManufacturer, upsIdentModel,
   --              upsIdentAgentSoftwareVersion, upsIdentName,
   --              upsIdentAttachedDevices }

   OBJECT       upsIdentManufacturer
   DESCRIPTION
      "The value of the upsIdentManufacturer object MUST contain the
       name of the device manufacturer."

   OBJECT       upsIdentModel                       -- same as RFC 1628
   DESCRIPTION
      "The UPS Model designation."

   OBJECT       upsIdentAgentSoftwareVersion        -- same as RFC 1628
   DESCRIPTION
      "The UPS agent software version.
       This object may have the same value as the
       upsIdentUPSSoftwareVersion object."

   OBJECT       upsIdentName
   DESCRIPTION
      "The upsIdentName object identifies the UPS and its value SHOULD
       be provided in the device configuration file. If the
       upsIdentName value is not provided in the configuration file,
       the default value MUST be an empty string."

   OBJECT       upsIdentAttachedDevices
   DESCRIPTION
      "The upsIdentAttachedDevices MUST contain the list of 
       devices attached to the UPS power output.
       The value of the upsIdentAttachedDevices object SHOULD follow
       the naming conventions defined for CableLabs DHCP option 43
       sub-option 3.
       For example, if the eDOCSIS device is an E-MTA with an
       integrated eCM and an eMTA eSAFE, this object must contain the
       value 'ECM:EMTA' (without the single quotes)."


   --   upsFullBatteryGroup OBJECT-GROUP
   --    OBJECTS { upsBatteryStatus, upsSecondsOnBattery,
   --              upsEstimatedMinutesRemaining,
   --              upsEstimatedChargeRemaining }

   OBJECT       upsBatteryStatus
   SYNTAX     INTEGER {
       batteryNormal(2),
       batteryLow(3),
       batteryDepleted(4)
   }
   DESCRIPTION
      "The support of the upsBatteryStatus object value unknown(1) is
       not required."

   OBJECT       upsSecondsOnBattery
   DESCRIPTION
      "If the device is on battery power, the
       upsSecondsOnBattery object MUST return the elapsed time
       since the UPS last switched to battery power, or the
       time since the device was last restarted, whichever is
       less.
       The upsSecondsOnBattery object MUST return a value of 0 if the
       attached devices are not on battery power."

   OBJECT       upsEstimatedMinutesRemaining     -- same as RFC 1628
   DESCRIPTION
      "An estimate of the time to battery charge depletion
       under the present load conditions if the utility power
       is off and remains off, or if it were to be lost and
       remain off."

   OBJECT       upsEstimatedChargeRemaining      -- same as RFC 1628
   DESCRIPTION
      "An estimate of the battery charge remaining expressed
       as a percent of full charge."


--   upsBasicInputGroup OBJECT-GROUP
--       OBJECTS { upsInputLineBads, upsInputNumLines,
--                 upsInputFrequency, upsInputVoltage } 

   OBJECT       upsInputLineBads
   DESCRIPTION
      "The upsInputLineBads object MAY be supported."

   OBJECT       upsInputNumLines
   DESCRIPTION
      "The upsInputNumLines object specifies the number of input
       lines utilized in this device.
       For example, for an eDOCSIS E-MTA device with 1 battery pack
       and 1 AC power source, this object value must be 2."

   OBJECT       upsInputFrequency
   DESCRIPTION
      "The upsInputFrequency object MAY be supported."

   OBJECT       upsInputVoltage
   DESCRIPTION
      "The upsInputVoltage object MAY be supported."


--   upsBasicOutputGroup OBJECT-GROUP
--       OBJECTS { upsOutputSource, upsOutputFrequency,
--                 upsOutputNumLines, upsOutputVoltage }
 
   OBJECT       upsOutputSource
   SYNTAX INTEGER {
       none(2),
       normal(3),
       battery(5) 
   }
   DESCRIPTION
      "The devices capable of supporting battery backup and UPS
       functionality MUST support the upsOutputSource values of
       none(2), normal(3), battery(5). The upsOutputSource value of
       other(1) may be used to represent transient states."

   OBJECT       upsOutputFrequency
   DESCRIPTION
      "The upsOutputFrequency object MAY be supported."

   OBJECT       upsOutputNumLines
   DESCRIPTION
      "The upsOutputNumLines object specifies the number of output
       lines utilized in this eDOCSIS device.
       For example, for an eDOCSIS E-MTA devices with both the eCM and
       eMTA attached to the UPS, this object value must be 2."

   OBJECT        upsOutputVoltage
   DESCRIPTION
      "The upsOutputVoltage object MAY be supported."


--   upsBasicAlarmGroup OBJECT-GROUP
--       OBJECTS { upsAlarmsPresent, upsAlarmDescr, upsAlarmTime }

   OBJECT       upsAlarmsPresent                 -- same as RFC 1628
   DESCRIPTION
      "The upsAlarmsPresent object indicates the current number of
       active alarm conditions."
   
   OBJECT       upsAlarmDescr
   DESCRIPTION
      "The following well known alarm types MUST be supported by
       the CableLabs UPS capable devices:
          upsAlarmBatteryBad,
          upsAlarmOnBattery,
          upsAlarmLowBattery,
          upsAlarmDepletedBattery, 
          upsAlarmOutputOffAsRequested,
          upsAlarmUpsOutputOff,
          upsAlarmGeneralFault,
          upsAlarmAwaitingPower,
          upsAlarmShutdownPending,
          and upsAlarmShutdownImminent."

   OBJECT       upsAlarmTime                     -- same as RFC 1628
   DESCRIPTION
      "The upsAlarmTime object indicates the value of sysUpTime when
       the alarm condition was detected."


--   upsBasicControlGroup OBJECT-GROUP
--       OBJECTS { upsShutdownType, upsShutdownAfterDelay,
--                 upsStartupAfterDelay, upsRebootWithDuration,
--                 upsAutoRestart }

   OBJECT       upsShutdownType
   SYNTAX     INTEGER {
                         output(1)
                      }
   DESCRIPTION
      "The upsShutdownType object defines the nature of the action to
       be taken at the time when the countdown of the
       upsShutdownAfterDelay and upsRebootWithDuration object values
       reach zero. 
       The support for the upsShutdownType value system is not
       required (for CableLabs compliant devices, a system shutdown or
       reset can be achieved using other mechanisms."

   OBJECT       upsStartupAfterDelay
   SYNTAX     INTEGER (-1..604800) -- max range is 7 days or 604800s
   DESCRIPTION
      "The upsStartupAfterDelay MUST be supported.
       The CableLabs devices capable of support battery backup and UPS
       functionality MUST support a maximum upsStartupAfterDelay value
       of 604800 seconds, equivalent to 7 days."

   OBJECT       upsRebootWithDuration            -- same as RFC 1628
   DESCRIPTION
      "The upsRebootWithDuration controls a reboot procedure with
       a countdown. It also indicates whether a reboot procedure is in
       progress and the number of seconds remaining in the countdown."

   OBJECT       upsAutoRestart                   -- same as RFC 1628
   DESCRIPTION
      "The upsAutoRestart is only applicable for UPS system shutdown;
       it MAY be supported."


--   upsBasicConfigGroup OBJECT-GROUP
--       OBJECTS { upsConfigInputVoltage, upsConfigInputFreq,
--                 upsConfigOutputVoltage, upsConfigOutputFreq,
--                 upsConfigOutputVA, upsConfigOutputPower,
--                 upsConfigLowBattTime, upsConfigAudibleStatus }

   OBJECT       upsConfigInputVoltage 
   DESCRIPTION
      "The upsConfigInputVoltage MAY be supported."

   OBJECT       upsConfigInputFreq 
   DESCRIPTION
      "The upsConfigInputFreq MAY be supported."

   OBJECT       upsConfigOutputVoltage 
   DESCRIPTION
      "The upsConfigOutputVoltage MAY be supported."

   OBJECT       upsConfigOutputFreq 
   DESCRIPTION
      "The upsConfigOutputFreq MAY be supported."

   OBJECT       upsConfigOutputVA 
   DESCRIPTION
      "The upsConfigOutputVA MAY be supported."

   OBJECT       upsConfigOutputPower 
   DESCRIPTION
      "The upsConfigOutputPower MAY be supported."

   OBJECT       upsConfigLowBattTime             -- same as RFC 1628
   DESCRIPTION
      "The upsConfigLowBattTime specifies the value of
       upsEstimatedMinutesRemaining at which a lowBattery condition is
       declared.
       Implementation of all possible values may be onerous for some
       systems.  Consequently, not all possible values must be
       supported. However, at least two different
       manufacturer-selected values for upsConfigLowBattTime MUST be
       supported."

   OBJECT       upsConfigAudibleStatus 
   DESCRIPTION
      "The upsConfigAudibleStatus MAY be supported."

       ::= { clabUpsCompliances 1 }


   --
   -- Units of conformance for CableLabs UPS capable devices
   -- Adapted from RFC 1628, a column was added for CableLabs devices
   -- An 'x' in the column means the object MUST be supported; all the
   -- rest is optional and left for vendor decision.

   




-- Summary at a glance:

   --                                    subset  basic   adv CLAB-UPS  COMPLIANCE GROUP
   --                                                          MUST 
   --upsIdentManufacturer                  x       x       x    x     upsSubsetIdentGroup
   --upsIdentModel                         x       x       x    x     upsSubsetIdentGroup
   --upsIdentUPSSoftwareVersion                    x       x 
   --upsIdentAgentSoftwareVersion          x       x       x    x     upsSubsetIdentGroup  
   --upsIdentName                          x       x       x    x     upsSubsetIdentGroup
   --upsIdentAttachedDevices               x               x    x     upsSubsetIdentGroup
   --
   --upsBatteryStatus                      x       x       x    x     upsFullBatteryGroup 
   --upsSecondsOnBattery                   x       x       x    x     upsFullBatteryGroup
   --upsEstimatedMinutesRemaining                          x    x     upsFullBatteryGroup
   --upsEstimatedChargeRemaining                           x    x     upsFullBatteryGroup
   --upsBatteryVoltage
   --upsBatteryCurrent
   --upsBatteryTemperature
   --
   --upsInputLineBads                      x       x       x
   --upsInputNumLines                              x       x    x     upsBasicInputGroup
   --upsInputFrequency                             x       x
   --upsInputVoltage                               x       x
   --upsInputCurrent
   --upsInputTruePower
   --
   --upsOutputSource                       x       x       x    x     upsBasicOutputGroup  
   --upsOutputFrequency                            x       x
   --upsOutputNumLines                             x       x    x     upsBasicOutputGroup 
   --upsOutputVoltage                              x       x
   --upsOutputCurrent                                      x
   --upsOutputPower                                        x
   --upsOutputPercentLoad                                  x     
   --
   --
   --upsBypassFrequency                            x       x 
   --upsBypassNumLines                             x       x
   --upsBypassVoltage                              x       x
   --upsBypassCurrent
   --upsBypassPower
   --
   --
   --upsAlarmsPresent                      x       x       x   x      upsBasicAlarmGroup 
   --upsAlarmDescr                         x       x       x   x      upsBasicAlarmGroup
   --upsAlarmTime                          x       x       x   x      upsBasicAlarmGroup
   --
   --upsTestId                                     x       x  
   --upsTestSpinLock                               x       x
   --upsTestResultsSummary                         x       x
   --upsTestResultsDetail                          x       x
   --upsTestStartTime                              x       x
   --upsTestElapsedTime                            x       x
   --
   --upsShutdownType                       x       x       x   x       upsBasicControlGroup      
   --upsShutdownAfterDelay                 x       x       x   x       upsBasicControlGroup
   --upsStartupAfterDelay                          x       x   x       upsBasicControlGroup
   --upsRebootWithDuration                         x       x   x       upsBasicControlGroup
   --upsAutoRestart                        x       x       x
   --
   --upsConfigInputVoltage                 x       x       x  
   --upsConfigInputFreq                    x       x       x  
   --upsConfigOutputVoltage                x       x       x  
   --upsConfigOutputFreq                   x       x       x  
   --upsConfigOutputVA                     x       x       x
   --upsConfigOutputPower                  x       x       x
   
   --upsConfigLowBattTime                                      x        upsBasicConfigGroup

END
