-- ****************************************************************************
-- *
-- * Alpha Technologies, Inc.
-- *
-- * NAME : ATI-MPSPS-MIB.txt
-- *
-- * ALPHA PART NUMBER : TBD
-- *
-- * SUMMARY : This is the small power supply generic data MIB.
-- *   Entry point is 1.3.6.1.4.1.926.1.4.2.1
-- *
-- * Revision History:
-- *
-- * 0.01.0  22-SEP-2008  Bill Crawford
-- *           Draft for review
-- *           
-- ****************************************************************************
ATI-MPSPS-MIB DEFINITIONS ::= BEGIN

IMPORTS
    atiMPSps
        FROM ATI-PRODUCT-PLATFORMS-MIB
    OBJECT-TYPE
        FROM RFC-1212
    ;

atiMpsInputVoltage OBJECT-TYPE
     SYNTAX INTEGER ( 0..65535 )
     ACCESS read-only
     STATUS optional
     DESCRIPTION
          "Scaled representation of input 'line' or 'grid' voltage.  This is an 
           RMS value in 1/100 Volt (10mV) units. MIB resolution is rounded
           to the nearest 1/10 volt."
     ::= { atiMPSps 1 }


atiMpsOutputVoltage OBJECT-TYPE
     SYNTAX INTEGER ( 0..65535 )
     ACCESS read-only
     STATUS mandatory
     DESCRIPTION
          "Power supply output voltage in 1/100 Volts (10mV) units.
           MIB resolution is rounded to 1/10 volt."
     ::= { atiMPSps 2 }


atiMpsOutputPower OBJECT-TYPE
     SYNTAX INTEGER ( 0..65535 )
     ACCESS read-only
     STATUS mandatory
     DESCRIPTION
          "Power supply output power in 1/100 Watts (10mW) units.
           MIB resolution is rounded to 1/10 Watt."
     ::= { atiMPSps 3 }


atiMpsBatteryVoltage OBJECT-TYPE
     SYNTAX INTEGER ( 0..65535 )
     ACCESS read-only
     STATUS mandatory
     DESCRIPTION
          "Power supply total string battery voltage in 1/100 Volts (10mV) units.
           MIB resolution is rounded to 1/10 volt."
     ::= { atiMPSps 4 }


atiMpsBatteryTemp OBJECT-TYPE
     SYNTAX INTEGER ( 0..65535 )
     ACCESS read-only
     STATUS mandatory
     DESCRIPTION
          "Power supply battery temperature in 1 degree Celsius units.
           This value is offset by -100 degrees Celsius."
     ::= { atiMPSps 5 }


atiMpsBatteryCurrent OBJECT-TYPE
     SYNTAX INTEGER ( 0..65535 )
     ACCESS read-only
     STATUS mandatory
     DESCRIPTION
          "Power supply battery current in 1/100 Amps (10mA) units.
           This value is offset by -3 Amps."
     ::= { atiMPSps 6 }


atiMpsBatteryPercentCharge OBJECT-TYPE
     SYNTAX INTEGER ( 0..65535 )
     ACCESS read-only
     STATUS mandatory
     DESCRIPTION
          "Power supply battery percent charge remaining in 1% units."
     ::= { atiMPSps 7 }

END
