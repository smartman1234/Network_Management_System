-- ****************************************************************************
-- *
-- * Alpha Technologies, Inc.
-- *
-- * NAME : ATI-ROOT-MIB.txt
-- *
-- * ALPHA PART NUMBER : TBD
-- *
-- * SUMMARY : This is the root MIB for MIBs defined by Alpha Technologies
-- *   INC as differentiated from Alpha Technologies LTD.  This allows the
-- *   sub-level components to be managed in a manner that allows individual
-- *   developers to work on sections without concern that they will define
-- *   overlapping OIDs.
-- *
-- *   The root OID for this file is 1.3.6.1.4.1.926.1
-- *
-- * Revision History:
-- *
-- * 0.01.0  22-SEP-2008  Bill Crawford
-- *         Draft for review
-- * 0.01.0  02-MAR-2009  Bill Crawford
-- *         Renamed {alphaTechInc 1} to atiLegacyReserved01
-- *
-- ****************************************************************************
ATI-ROOT-MIB DEFINITIONS ::= BEGIN

IMPORTS
    alphaTechInc
        FROM ATL-ROOT-MIB
;

-- Unfortunately we/I have no recollection of what the name of this origional
-- MIB branch was named.
atiLegacyReserved01       OBJECT IDENTIFIER ::= { alphaTechInc  1 }

-- Intended primarily for generic table information.  The only thing we
-- currently support is the generic CIB tables so we define this additional
-- branch.
atiTables                 OBJECT IDENTIFIER ::= { alphaTechInc  2 }
atiManagement             OBJECT IDENTIFIER ::= { alphaTechInc  3 }
atiProductPlatforms       OBJECT IDENTIFIER ::= { alphaTechInc  4 }
alphaTechIncIDs           OBJECT IDENTIFIER ::= { alphaTechInc 99 }

END
