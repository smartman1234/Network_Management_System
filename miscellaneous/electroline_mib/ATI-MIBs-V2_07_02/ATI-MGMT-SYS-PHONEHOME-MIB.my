ATI-MGMT-SYS-PHONEHOME-MIB DEFINITIONS ::= BEGIN

IMPORTS
    atiMgmtSysPhoneHome 
        FROM ATI-MGMT-SYS-MIB
    OBJECT-TYPE
        FROM RFC-1212
    NetworkAddress
        FROM RFC1155-SMI
;

atiMgmtSysPhoneHomeIp OBJECT-TYPE
    SYNTAX     NetworkAddress 
    ACCESS     read-write
    STATUS     mandatory
    DESCRIPTION "Address for the Phone Home Frame"
    ::= { atiMgmtSysPhoneHome 1 }

atiMgmtSysPhoneHomeForce OBJECT-TYPE
    SYNTAX     INTEGER { noop(1), force(2) }
    ACCESS     read-write 
    STATUS     mandatory
    DESCRIPTION "Forces one PhoneHome message regardless of timers"
    ::= { atiMgmtSysPhoneHome 2 }

atiMgmtSysPhoneHomeTimer OBJECT-TYPE
    SYNTAX  TimeTicks
    ACCESS  read-only
    STATUS  mandatory
    DESCRIPTION "Time since last frame xmited, zero means never xmited"
    ::= { atiMgmtSysPhoneHome 3 }

END
